module l3vpn {

  namespace "http://mtn.com/l3vpn";
  prefix l3vpn;

  import ietf-inet-types {
    prefix inet;
  }
  import tailf-common {
    prefix tailf;
  }
  import tailf-ncs {
    prefix ncs;
  }
  //import vrf-config {
//	prefix vrf-config;
 // }
import tailf-ned-cisco-ios-xr { prefix cisco-ios-xr; }
  include l3vpn-params;

  description
    "L3 VPN Service Package";

  revision 2018-05-03 {
    description
      "v1.0";
  }



  augment /ncs:services {
    list mtn-l3vpn {
		description "L3 VPN Service";
		uses ncs:service-data;
		//SERVICE-POINT
		ncs:servicepoint l3vpn-servicepoint;

		//uses l3-interface-params;

		key customer-id;
		leaf customer-id {
			tailf:info "Unique customer id";
			tailf:cli-allow-range;
			type string;
		}

		list device {
			key device;
			uses l3-service-input-params {
				refine "device" {
					tailf:cli-suppress-range;
				}
			}

		}
    }
  }
}
